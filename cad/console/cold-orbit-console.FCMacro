# -*- coding: utf-8 -*-
"""
Cold Orbit - full bridge console.
FreeCAD parametric macro.  Tools > Macro > Execute.

Builds every panel from section 7 of the master plan as a separate solid,
placed in its seated-player position.

COORDINATE SYSTEM (mm), player-centric:
    X   +right / -left, 0 = player centreline
    Y   +forward, away from the player
    Z   +up from floor
Origin (0,0,0) is the floor directly below the player's eye line.

ORIENTATION, given per panel as (yaw, tilt):
    yaw   rotation about Z.  0 = facing straight back at the player.
    tilt  0 = vertical.  +ve leans the top away so the face points downward
          (overhead).  -ve lays it back so the face points upward (consoles).

NOTE: this is still mostly a LAYOUT model - most panels are floating faces,
no frame, no mounts, no joinery.  The WALLS section is a first, partial
exception, closing the gap between HOTAS, the tilt-screen, comms and the
hardpoint panels with real touching geometry, not placeholder boxing:
  - HOTAS: footprint pinned exactly between the tilt-screen's front edge
    and the main-screen/comms row, with a triangular Side (flush against
    the tilt-screen) and rectangular Back (flush against comms).
  - Propulsion/FTL: no longer flat panels facing the player - each is two
    flat triangular facets (Back/Front) meeting along a diagonal seam,
    because the four real corners they have to touch (HOTAS, the hardpoint
    panel, and comms' edge) aren't coplanar. Both facets carry real
    controls now, via TriPanel (WALLS section) - a Face authored in a
    local (u,v) grid, same as every other panel, then mapped onto the
    triangle and trimmed to it.
  - Engineering: sized to the same width as cameras, so its outer corners
    share a point with both cameras' top corners and the top hardpoint
    panels' inner-top corner. Outboard of that shared point, engineering's
    own angled face and the hardpoint panels' outward yaw diverge - filled
    solid per side (EngLeftFill/RightFill): one flat facet facing the seat,
    the bulk above and behind it, hugging the hardpoint box.
Everything else is still just floating faces; woodwork/joinery proper
comes later still.

Control legends are etched (shallow pocket) into the front face of each
panel.  All the wording lives in the LABELS dict - edit it there, nowhere
else.  Wording follows the v24 doc, section 7.
"""
import math
import os

import FreeCAD as App
import Part

# ================================================================ PARAMETERS
# >>> MEASURE AGAINST REAL PARTS BEFORE CUTTING ANYTHING <<<
PLY_T    = 5.0      # panel thickness
BOX_D    = 200.0    # enclosure depth rearward from panel front face -- MEASURE

EYE_Z    = 1150.0   # seated eye height above floor
MAIN_Y   = 750.0    # main panel plane, forward of the player
Z_SCREEN = EYE_Z - 60.0

SCREEN_W, SCREEN_H = 597.0, 336.0   # 27" visible area   -- MEASURE
TS_W, TS_H         = 340.0, 190.0   # touchscreen visible area -- MEASURE
HP_SCREEN          = 140.0          # hardpoint panel screen aperture

# Component hole diameters -- PLACEHOLDERS, verify against real parts
D_TOGGLE   = 12.0   # toggle switch bushing
D_BUTTON   = 16.0   # momentary push button
D_BTN_SM   = 14.0   # small button (hardpoint soft keys)
D_BTN_LG   = 22.0   # large / illuminated button
BTN_SQ     = 34.0   # square illuminated button (comms warn/caution + nav)
D_ESTOP    = 30.0   # emergency stop, SCRAM
D_LED      = 5.0
D_LED_SM   = 3.0
D_KNOB     = 22.0   # rotary knob shaft + bush
D_ENCODER  = 8.0    # rotary encoder shaft
D_MOUNT    = 4.5    # M4 clearance

CUT_T = PLY_T * 4.0
CUT_Z = -PLY_T

# ================================================================ COLOUR
COL_WOOD      = (0.55, 0.55, 0.55)   # painted grey - not bare ply
COL_WOOD_DARK = (0.35, 0.35, 0.35)   # darker grey, optional variation -- not
                                     # yet applied anywhere; one grey tone
                                     # across everything for this pass.

# ================================================================ COMPONENTS
# Physical facts + placeholders for the two component types Phase 1 renders.
# Square backlit button (cameras, touchscreen mode-select, comms panels).
# NOTE: the panel cutout is BTN_SQUARE_CUTOUT (round, sized to the
# component's actual body) - BTN_SQUARE_FACE/BTN_SQ is the visible cap only,
# which sits proud and overlaps the wood around the smaller round hole. The
# panels' own hole-cutting code used to cut BTN_SQ (34mm) square holes
# directly - that was a guide sized to the cap, not the real part, and has
# been corrected to cut BTN_SQUARE_CUTOUT instead (see f_cameras/f_ts_modes/
# f_comms below).
BTN_SQUARE_FACE   = BTN_SQ    # cap face width/height (mm) -- aliased to the
                              # pre-existing BTN_SQ constant so the two can't
                              # drift apart independently.
BTN_SQUARE_CUTOUT = 23.5      # panel hole diameter (mm) for the round body
BTN_SQUARE_DEPTH  = 30.0      # body depth behind panel (mm) -- PLACEHOLDER, MEASURE
COL_BTN_BODY      = (0.2, 0.2, 0.2)
COL_BTN_BLUE      = (0.1, 0.4, 1.0)    # cameras / ts_modes cap colour
COL_BTN_WHITE     = (1.0, 1.0, 1.0)    # comms cap colour -- same button, no backlight colour confirmed yet

# Guarded toggle switch "Gebildet" (every ARM position, all panels).
TOG_BODY_W    = 13.0   # body width (mm) -- PLACEHOLDER, MEASURE
TOG_BODY_D    = 19.0   # body depth front-to-back (mm) -- PLACEHOLDER, MEASURE
TOG_BODY_H    = 30.0   # body height behind panel (mm) -- PLACEHOLDER, MEASURE
TOG_CUTOUT    = D_TOGGLE   # panel hole diameter (mm) -- aliased to the
                           # existing D_TOGGLE cutout above (both 12.0mm);
                           # PLACEHOLDER, MEASURE
TOG_BAT_L     = 20.0   # bat lever length (mm) -- PLACEHOLDER, MEASURE
TOG_GUARD_H   = 50.0   # guard flap length, hinge to tip (mm) -- PLACEHOLDER, MEASURE
TOG_GUARD_W   = 20.0   # guard width (mm) -- PLACEHOLDER, MEASURE
COL_TOG_BODY  = (0.15, 0.15, 0.15)   # black
COL_TOG_BAT   = (0.7, 0.7, 0.7)      # grey
COL_TOG_GUARD = (0.85, 0.10, 0.10)   # red

# ================================================================ STARTUP DIALOG
# One prompt, up front, for both run-time choices this macro asks about:
# whether to render components (buttons, switches) and how far to separate
# panels for an exploded view. They used to fire at two different points -
# this one, RENDER_COMPONENTS, had to run before everything downstream that
# gates on it (the WALLS section below reads it while building the
# FTL/Propulsion TriPanels), while the explode prompt ran much later, right
# before panels are actually instantiated. Combined here, both are decided
# before any geometry gets built, which is also the earliest either one
# could possibly run.
try:
    from PySide2 import QtWidgets, QtCore
except ImportError:
    from PySide import QtGui as QtWidgets, QtCore

_qapp = QtWidgets.QApplication.instance() or QtWidgets.QApplication([])
_dlg  = QtWidgets.QDialog()
_dlg.setWindowTitle("Cold Orbit Console")
_dlg_box = QtWidgets.QVBoxLayout()
_render_check = QtWidgets.QCheckBox("Render components (buttons, switches)")
_render_check.setChecked(True)
_sep_label = QtWidgets.QLabel("Panel separation: 0 mm")
_slider = QtWidgets.QSlider(QtCore.Qt.Horizontal)
_slider.setRange(0, 100)
_slider.setValue(0)
_slider.valueChanged.connect(lambda v: _sep_label.setText("Panel separation: %d mm" % v))
_btns = QtWidgets.QDialogButtonBox(
    QtWidgets.QDialogButtonBox.Ok | QtWidgets.QDialogButtonBox.Cancel)
_btns.accepted.connect(_dlg.accept)
_btns.rejected.connect(_dlg.reject)
_dlg_box.addWidget(_render_check)
_dlg_box.addWidget(_sep_label)
_dlg_box.addWidget(_slider)
_dlg_box.addWidget(_btns)
_dlg.setLayout(_dlg_box)

if not _dlg.exec_():
    raise SystemExit("Macro cancelled")

RENDER_COMPONENTS = _render_check.isChecked()
EXPLODE = float(_slider.value())          # mm of separation
_EXPLODE_ORIGIN = App.Vector(0.0, 0.0, EYE_Z)

# ================================================================ LETTERING
SHOW_LABELS  = True     # False = plain panels, no etching
ETCH_D       = 0.6      # etch pocket depth into the front face
TEXT_GAP     = 3.5      # clear space between a control edge and its legend
TITLE_INSET  = 6.0      # panel title, in from the panel edge

# Cap heights (mm).  Approximate - the font is scaled so capitals land here.
TEXT_H_TITLE = 7.0      # panel title
TEXT_H_HDR   = 5.0      # column / group headers
TEXT_H       = 3.6      # normal control legend
TEXT_H_TINY  = 2.4      # cycle arrows, missile-type numerals

CAP_RATIO    = 0.73     # Oswald cap height as a fraction of nominal font size
                        # (font-specific - adjust if you swap FONT_FILE and the
                        # etched capitals don't measure TEXT_H)

# Oswald - condensed, which is what keeps the longer legends inside a column.
# Leave FONT_FILE empty to auto-pick the first candidate that exists.
# Note: the variable-weight file etches at its default weight; drop a static
# Oswald-Bold.ttf in and point FONT_FILE at it if you want heavier strokes.
FONT_FILE       = ""
FONT_CANDIDATES = [
    os.path.expanduser("~/Library/Fonts/Oswald-VariableFont_wght.ttf"),
    os.path.expanduser("~/Library/Fonts/Oswald-Bold.ttf"),
    os.path.expanduser("~/Library/Fonts/Oswald-Regular.ttf"),
    "/Library/Fonts/Oswald-VariableFont_wght.ttf",
    "/usr/share/fonts/truetype/oswald/Oswald-VariableFont_wght.ttf",
    "C:/Windows/Fonts/Oswald-VariableFont_wght.ttf",
    # Last-ditch fallbacks so the macro still runs on a machine without Oswald.
    "/System/Library/Fonts/Supplemental/Arial Narrow Bold.ttf",
    "/usr/share/fonts/truetype/dejavu/DejaVuSans-Bold.ttf",
    "C:/Windows/Fonts/arialbd.ttf",
]

# ================================================================ LABELS
# Every word etched on the console.  Wording from v24 sections 7.1 - 7.9.
LABELS = {
    # --- 7.1 turrets ---------------------------------------------------
    "turrets_title":        "TURRETS",
    "turrets_col_l":        "DORSAL",
    "turrets_col_r":        "VENTRAL",
    "turrets_arm":          "ARM",
    "turrets_ammo":         "AMMO",
    "turrets_target":       "TARGET",
    "turrets_target_prev":  "<",
    "turrets_target_next":  ">",
    "turrets_lock":         "LOCK",
    "turrets_reload":       "RELOAD",
    "turrets_mode":         "FIRE MODE",
    "turrets_mode_up":      "LETHAL",
    "turrets_mode_dn":      "NON-LETHAL",

    # --- 7.2 missiles --------------------------------------------------
    "missiles_title":       "MISSILES",
    "missiles_col_l":       "FORE",
    "missiles_col_r":       "AFT",
    "missiles_arm":         "ARM",
    "missiles_ammo":        "AMMO TYPE",
    "missiles_ammo_prev":   "<",
    "missiles_ammo_next":   ">",
    "missiles_types":       ("1", "2", "3", "4"),   # per-type indicator dots
    "missiles_load":        "LOAD",
    "missiles_target":      "TARGET",
    "missiles_target_prev": "<",
    "missiles_target_next": ">",
    "missiles_lock":        "LOCK",
    "missiles_fire":        "FIRE",

    # --- 7.3 cameras ---------------------------------------------------
    # Short forms of the doc's names (External/chase, Dorsal turret cam,
    # Ventral turret cam, Docking/proximity, Damage inspection).
    # Left-to-right order is still open in 7.3 - reorder here when it lands.
    "cameras_title":        "CAMERAS",
    "cameras_views":        ("FORWARD", "AFT", "CHASE", "DORSAL",
                             "VENTRAL", "DOCKING", "DAMAGE"),

    # --- 7.4 touchscreen mode select -----------------------------------
    # Left-to-right order also still open in 7.4.
    "ts_modes_title":       "MODE SELECT",
    "ts_modes_modes":       ("ENGINEERING", "PROPULSION", "FTL", "TURRETS",
                             "MISSILES", "COMMS", "HARDPOINTS", "MAP"),

    # --- 7.5 comms -----------------------------------------------------
    # No panel title: master warn/caution and volume are ship-wide, not
    # comms-specific (7.5) - so the LCD carries the COMMS legend instead.
    "comms_title":          "",
    "comms_warn":           "MASTER WARN",
    "comms_caution":        "MASTER CAUTION",
    "comms_volume":         "VOLUME",
    "comms_clock":          "CLOCK",
    "comms_lcd":            "COMMS",
    "comms_msg":            "NEW MESSAGE",
    "comms_up":             "UP",
    "comms_select":         "SELECT",
    "comms_down":           "DOWN",

    # --- 7.6 FTL -------------------------------------------------------
    "ftl_title":            "FTL",
    "ftl_dest":             "DEST",
    "ftl_dest_prev":        "<",
    "ftl_dest_next":        ">",
    "ftl_arm":              "ARM",
    "ftl_vector":           "VECTOR",
    "ftl_jump":             "JUMP",

    # --- 7.7 propulsion ------------------------------------------------
    "prop_title":           "PROPULSION",
    "prop_cutoff":          "EMERGENCY CUTOFF",
    "prop_ignition":        "IGNITION",
    "prop_arm":             "ARM",
    "prop_mix":             "PROPELLANT MIX",
    "prop_mix_lean":        "LEAN",
    "prop_mix_rich":        "RICH",
    "prop_temp":            "ENGINE TEMP",
    "prop_rcs":             "RCS",
    "prop_dampeners":       "DAMPENERS",
    "prop_reverse":         "REVERSE",

    # --- 7.8 engineering -----------------------------------------------
    "eng_title":            "ENGINEERING",
    "eng_row_repair":       "REPAIR",      # row legend, sits in the group gap
    "eng_row_alloc":        "POWER",       # row legend, allocation encoders
    "eng_reactor":          "REACTOR",
    "eng_output":           "OUTPUT",
    "eng_scram":            "SCRAM",
    "eng_total":            "TOTAL POWER",
    "eng_systems":          ("WEAPONS", "ENGINES", "FTL",
                             "UTIL 1", "UTIL 2", "UTIL 3", "UTIL 4"),

    # --- 7.9 generic hardpoint -----------------------------------------
    # Soft keys are deliberately unlabelled: 7.9 has the screen render each
    # key's label beside it, LSK-style.  Fill these in only if you want
    # etched key indices as well.
    "hardpoint_title":      "HARDPOINT",
    "hardpoint_arm":        "ARM",
    "hardpoint_lcd":        "MODULE ID",
    "hardpoint_softkeys":   ("", "", "", "", "", "", "", ""),

    # --- panels with nothing to letter ---------------------------------
    "screen_title":         "",
    "touchscreen_title":    "",
    "hotas_title":          "",
}

# ================================================================ SIZES
SZ = {
    "screen":      (687.0, 426.0),
    "cameras":     (0.0,    90.0),   # width derived below
    "comms":       (0.0,   150.0),   # width derived below
    "turrets":     (260.0, 426.0),
    "missiles":    (260.0, 426.0),
    "ts_modes":    (400.0,  80.0),
    "touchscreen": (400.0, 250.0),
    "hotas":       (200.0, 260.0),
    "hardpoint":        (260.0,   0.0),   # height derived below
    # Propulsion/FTL aren't flat Face panels any more - see TriPanel in the
    # WALLS section, sized directly from real touch-point geometry there.
    "engineering":      (0.0,   300.0),   # width derived below (screen-width centre)
    "engineering_ext":  (0.0,   300.0),   # width derived below (blank side extensions)
}

# Cameras and comms match the screen width only - no dead overhang beside
# turrets/missiles. Engineering still spans the full main-group width so its
# outer corners land on cameras' top corners.
_MAIN_GROUP_W = SZ["turrets"][0] + SZ["screen"][0] + SZ["missiles"][0]
SZ["cameras"] = (SZ["screen"][0], SZ["cameras"][1])
SZ["comms"]   = (SZ["screen"][0], SZ["comms"][1])
SZ["engineering"] = (SZ["screen"][0], SZ["engineering"][1])
_eng_ext_w = (_MAIN_GROUP_W - SZ["screen"][0]) / 2.0
SZ["engineering_ext"] = (_eng_ext_w, SZ["engineering"][1])

# Turrets and missiles grow to fill the full vertical span beside cameras,
# screen, and comms - top edge flush with cameras' top, bottom edge flush
# with comms' bottom.
_weapons_h = SZ["cameras"][1] + SZ["screen"][1] + SZ["comms"][1]
SZ["turrets"]  = (SZ["turrets"][0],  _weapons_h)
SZ["missiles"] = (SZ["missiles"][0], _weapons_h)

# The 4 hardpoint panels flank turrets/missiles two-a-side, stacked to touch
# and together reach from top-of-cameras to bottom-of-comms, split in half.
SZ["hardpoint"] = (SZ["hardpoint"][0],
                   (SZ["cameras"][1] + SZ["screen"][1] + SZ["comms"][1]) / 2.0)


# ================================================================ LETTERING
def _resolve_font():
    """First usable font file, or '' if none of the candidates exist."""
    for path in [FONT_FILE] + FONT_CANDIDATES:
        if path and os.path.isfile(path):
            return path
    return ""


_FONT = _resolve_font() if SHOW_LABELS else ""
_TEXT_CACHE = {}

doc = App.ActiveDocument or App.newDocument("ColdOrbitConsole")

for _obj in list(doc.Objects):
    doc.removeObject(_obj.Name)
doc.recompute()

if SHOW_LABELS and _FONT:
    import Draft
    _shapestring = getattr(Draft, "make_shapestring", None) or Draft.makeShapeString


def _text_shape(string, cap_h):
    """Flat character faces on the XY plane, origin at the baseline start."""
    key = (string, round(cap_h, 4))
    if key not in _TEXT_CACHE:
        obj = _shapestring(String=string, FontFile=_FONT,
                           Size=cap_h / CAP_RATIO, Tracking=0.0)
        doc.recompute()
        _TEXT_CACHE[key] = obj.Shape.copy()
        doc.removeObject(obj.Name)
    return _TEXT_CACHE[key].copy()


# ================================================================ FACE
class Face(object):
    """A flat panel built centred on its own local origin."""

    def __init__(self, key):
        self.w, self.h = SZ[key]
        self.cuts = []
        self.texts = []
        self.components = []

    # -- cutouts --------------------------------------------------------
    def hole(self, x, y, dia):
        self.cuts.append(Part.makeCylinder(
            dia / 2.0, CUT_T, App.Vector(x, y, CUT_Z)))

    def slot(self, x, y, w, h):
        self.cuts.append(Part.makeBox(
            w, h, CUT_T, App.Vector(x - w / 2.0, y - h / 2.0, CUT_Z)))

    def square(self, x, y, size):
        self.slot(x, y, size, size)

    def row(self, xs, y, dia):
        for x in xs:
            self.hole(x, y, dia)

    def mounts(self, inset=15.0):
        for x in (-self.w / 2 + inset, self.w / 2 - inset):
            for y in (-self.h / 2 + inset, self.h / 2 - inset):
                self.hole(x, y, D_MOUNT)

    # -- components -------------------------------------------------------
    # Registered here regardless of RENDER_COMPONENTS (cheap - just a list
    # append); the flag is checked once, where the geometry actually gets
    # built and placed.
    def button_square(self, x, y, cap_colour=None):
        """Register a square backlit button component centred on (x, y).
        `cap_colour` overrides COL_BTN_BLUE - e.g. comms' white caps."""
        self.components.append(("button_square", x, y, cap_colour))

    def toggle_guarded(self, x, y):
        """Register a guarded toggle-switch component centred on (x, y)."""
        self.components.append(("toggle_guarded", x, y, None))

    # -- lettering ------------------------------------------------------
    def text(self, x, y, string, cap_h=None, halign="center", valign="bottom"):
        """Etch `string`, positioning its bounding box against (x, y)."""
        if string:
            self.texts.append((x, y, string, cap_h or TEXT_H, halign, valign))

    def text_above(self, x, y, clear, string, cap_h=None, halign="center"):
        """Legend above a control centred on (x, y); `clear` = its half-height."""
        self.text(x, y + clear + TEXT_GAP, string, cap_h, halign, "bottom")

    def text_below(self, x, y, clear, string, cap_h=None, halign="center"):
        self.text(x, y - clear - TEXT_GAP, string, cap_h, halign, "top")

    def text_right(self, x, y, clear, string, cap_h=None):
        self.text(x + clear + TEXT_GAP, y, string, cap_h, "left", "middle")

    def text_left(self, x, y, clear, string, cap_h=None):
        self.text(x - clear - TEXT_GAP, y, string, cap_h, "right", "middle")

    def title(self, string, cap_h=None, halign="center", top=True,
              inset=TITLE_INSET, x=None):
        y = self.h / 2 - inset if top else -self.h / 2 + inset
        if x is None:
            x = {"center": 0.0,
                 "left":  -self.w / 2 + 2 * inset,
                 "right":  self.w / 2 - 2 * inset}[halign]
        self.text(x, y, string, cap_h or TEXT_H_TITLE, halign,
                  "top" if top else "bottom")

    def _etch(self, x, y, string, cap_h, halign, valign):
        shape = _text_shape(string, cap_h)
        bb = shape.BoundBox
        dx = {"left":   x - bb.XMin,
              "right":  x - bb.XMax,
              "center": x - (bb.XMin + bb.XMax) / 2.0}[halign]
        dy = {"bottom": y - bb.YMin,
              "top":    y - bb.YMax,
              "middle": y - (bb.YMin + bb.YMax) / 2.0,
              "baseline": y}[valign]
        shape.translate(App.Vector(dx, dy, PLY_T - ETCH_D))
        # Over-extrude past the front face so the boolean always breaks it.
        return shape.extrude(App.Vector(0, 0, ETCH_D + 1.0))

    # -- output ---------------------------------------------------------
    def solid(self):
        blank = Part.makeBox(self.w, self.h, PLY_T,
                             App.Vector(-self.w / 2, -self.h / 2, 0))
        cuts = list(self.cuts)
        if SHOW_LABELS and _FONT:
            for spec in self.texts:
                cuts.append(self._etch(*spec))
        if not cuts:
            return blank
        return blank.cut(Part.makeCompound(cuts))


# ================================================================ COMPONENT GEOMETRY
# Simplified solids for the two component types Phase 1 covers - enough to
# check fit and show colour, not photorealistic. Built in a panel's own
# local (x, y) coords, with the panel's front face at local z = PLY_T and
# local +z pointing back at the player (see placement()) - so a component
# behind the panel (into the enclosure) extends toward -z, and one proud of
# the panel (toward the player) extends past +PLY_T. Callers reuse whatever
# world transform already moves the panel itself; see component_shapes().
def _button_square_shapes(x, y, cap_colour):
    """Square backlit button: round body behind the panel (through the
    BTN_SQUARE_CUTOUT hole), square cap proud of the front face."""
    body = Part.makeCylinder(BTN_SQUARE_CUTOUT / 2.0, BTN_SQUARE_DEPTH,
                             App.Vector(x, y, -BTN_SQUARE_DEPTH))
    cap = Part.makeBox(BTN_SQUARE_FACE, BTN_SQUARE_FACE, 3.0,
                       App.Vector(x - BTN_SQUARE_FACE / 2.0,
                                  y - BTN_SQUARE_FACE / 2.0, PLY_T))
    return [(body, COL_BTN_BODY), (cap, cap_colour or COL_BTN_BLUE)]


def _toggle_guarded_shapes(x, y, _extra):
    """Guarded toggle, shown in its safe/OFF state: black body behind the
    panel, grey bat angled down toward OFF, red guard flap hinged near the
    top and angled down over the toggle."""
    body = Part.makeBox(TOG_BODY_W, TOG_BODY_D, TOG_BODY_H,
                        App.Vector(x - TOG_BODY_W / 2.0, y - TOG_BODY_D / 2.0,
                                   -TOG_BODY_H))
    bat = Part.makeCylinder(2.0, TOG_BAT_L, App.Vector(x, y, PLY_T))
    bat.rotate(App.Vector(x, y, PLY_T), App.Vector(1, 0, 0), 30.0)

    # Guard: built hanging straight down from its hinge (flush against the
    # panel), then tilted -50 degrees about that hinge so the free end lifts
    # clearly forward, off the panel face - a shallower angle read as flush
    # from most view angles instead of visibly standing off the surface.
    guard = Part.makeBox(TOG_GUARD_W, TOG_GUARD_H, 4.0,
                         App.Vector(x - TOG_GUARD_W / 2.0, y, PLY_T + 2.0))
    guard_hinge = App.Vector(x, y + TOG_GUARD_H, PLY_T + 2.0)
    guard.rotate(guard_hinge, App.Vector(1, 0, 0), -50.0)
    return [(body, COL_TOG_BODY), (bat, COL_TOG_BAT), (guard, COL_TOG_GUARD)]


_COMPONENT_BUILDERS = {
    "button_square":  _button_square_shapes,
    "toggle_guarded": _toggle_guarded_shapes,
}


def component_shapes(kind, x, y, extra=None):
    """(shape, ShapeColor) pairs, in local panel coords, for one registered
    component instance. `extra` is the per-instance override registered
    alongside (x, y) - e.g. button_square's cap_colour."""
    return _COMPONENT_BUILDERS[kind](x, y, extra)


def spread(n, pitch):
    """n evenly spaced coordinates centred on zero."""
    return [(i - (n - 1) / 2.0) * pitch for i in range(n)]


# ================================================================ PANELS
def f_screen():
    f = Face("screen")
    f.slot(0, 0, SCREEN_W, SCREEN_H)
    f.title(LABELS["screen_title"])
    f.mounts(22)
    return f


def f_cameras():
    """7.3 - Fwd, Aft, Chase, Dorsal, Ventral, Docking, Damage.
    Square backlit buttons - the backlight is the selection indicator,
    so no separate LED cutout."""
    f = Face("cameras")
    L = LABELS
    xs = spread(7, 90.0)
    for x, name in zip(xs, L["cameras_views"]):
        f.hole(x, 0.0, BTN_SQUARE_CUTOUT)
        f.button_square(x, 0.0)
        f.text_above(x, 0.0, BTN_SQ / 2.0, name)
    f.title(L["cameras_title"], TEXT_H_HDR)
    f.mounts()
    return f


def f_comms():
    """7.5 - Master Warn/Caution, Volume, clock, LCD, msg LED, Up/Sel/Down.

    Panel is full main-panel-group width, but the controls stay clustered
    centrally - dead space at both ends rather than stretched to the edges.
    Left to right: volume top-left of the cluster, then the Select / Up-Down
    nav cluster, the LCD it drives, message LED and clock, with Master
    Warn/Caution on the right. Warn, caution, up, down and select are square
    illuminated buttons."""
    f = Face("comms")
    L = LABELS
    sq = BTN_SQ / 2.0

    f.hole(-294, 28, D_KNOB)            # master volume, top-left of cluster
    f.text_above(-294, 28, D_KNOB / 2.0, L["comms_volume"])

    # Nav cluster: Select outboard, Up/Down stacked to the right of it.
    f.hole(-214, 0, BTN_SQUARE_CUTOUT)  # select
    f.button_square(-214, 0, COL_BTN_WHITE)
    f.text_above(-214, 0, sq, L["comms_select"])
    f.hole(-164, 22, BTN_SQUARE_CUTOUT) # up
    f.button_square(-164, 22, COL_BTN_WHITE)
    f.text_above(-164, 22, sq, L["comms_up"])
    f.hole(-164, -22, BTN_SQUARE_CUTOUT) # down
    f.button_square(-164, -22, COL_BTN_WHITE)
    f.text_below(-164, -22, sq, L["comms_down"])

    f.slot(-14, 0, 190, 42)             # comms LCD
    f.text_above(-14, 0, 21.0, L["comms_lcd"])
    f.hole(-14, -30, D_LED)             # new message, below LCD
    f.text_below(-14, -30, D_LED / 2.0, L["comms_msg"])
    f.slot(145, 0, 90, 32)              # 7-seg clock
    f.text_above(145, 0, 16.0, L["comms_clock"])

    f.hole(285, 22, BTN_SQUARE_CUTOUT)  # master warn
    f.button_square(285, 22, COL_BTN_WHITE)
    f.text_above(285, 22, sq, L["comms_warn"])
    f.hole(285, -22, BTN_SQUARE_CUTOUT) # master caution
    f.button_square(285, -22, COL_BTN_WHITE)
    f.text_below(285, -22, sq, L["comms_caution"])

    f.title(L["comms_title"], TEXT_H_HDR, top=False)
    f.mounts()
    return f


def f_turrets():
    """7.1 - dorsal left / ventral right. Arm, Ammo, Target, Lock, Reload."""
    f = Face("turrets")
    L = LABELS
    rows = {"arm": 173, "ammo": 125, "target": 73, "lock": 35, "reload": -13}
    f.title(L["turrets_title"])
    for cx, hdr in ((-45.0, L["turrets_col_l"]), (45.0, L["turrets_col_r"])):
        f.text(cx, 199.0, hdr, TEXT_H_HDR, valign="top")

        f.hole(cx, rows["arm"], D_TOGGLE)
        f.toggle_guarded(cx, rows["arm"])
        f.text_above(cx, rows["arm"], D_TOGGLE / 2.0, L["turrets_arm"])

        f.slot(cx, rows["ammo"], 26, 10)
        f.text_above(cx, rows["ammo"], 5.0, L["turrets_ammo"])

        f.hole(cx - 22, rows["target"], D_BUTTON)
        f.hole(cx + 22, rows["target"], D_BUTTON)
        # Row legend centred, prev/next arrows over their own buttons.
        f.text_above(cx, rows["target"], D_BUTTON / 2.0, L["turrets_target"])
        f.text_above(cx - 22, rows["target"], D_BUTTON / 2.0,
                     L["turrets_target_prev"], TEXT_H_TINY)
        f.text_above(cx + 22, rows["target"], D_BUTTON / 2.0,
                     L["turrets_target_next"], TEXT_H_TINY)

        f.hole(cx, rows["lock"], D_LED)
        # Below, so it clears the target-select legend directly above it.
        f.text_below(cx, rows["lock"], D_LED / 2.0, L["turrets_lock"])

        f.hole(cx, rows["reload"], D_BUTTON)
        f.text_above(cx, rows["reload"], D_BUTTON / 2.0, L["turrets_reload"])

    # Shared fire mode: title, then the two switch positions above/below.
    f.hole(0, -163, D_TOGGLE)
    f.text_above(0, -163, D_TOGGLE / 2.0, L["turrets_mode_up"])
    f.text(0, -163 + D_TOGGLE / 2.0 + 2 * TEXT_GAP + TEXT_H,
           L["turrets_mode"], TEXT_H_HDR, valign="bottom")
    f.text_below(0, -163, D_TOGGLE / 2.0, L["turrets_mode_dn"])
    f.mounts()
    return f


def f_missiles():
    """7.2 - fore left / aft right. Arm, Ammo type, Load, Target, Lock, Fire."""
    f = Face("missiles")
    L = LABELS
    rows = {"arm": 177, "ammo": 129, "load": 83,
            "target": 37, "lock": 1, "fire": -45}
    f.title(L["missiles_title"])
    for cx, hdr in ((-45.0, L["missiles_col_l"]), (45.0, L["missiles_col_r"])):
        f.text(cx, 199.0, hdr, TEXT_H_HDR, valign="top")

        f.hole(cx, rows["arm"], D_TOGGLE)
        f.toggle_guarded(cx, rows["arm"])
        f.text_above(cx, rows["arm"], D_TOGGLE / 2.0, L["missiles_arm"])

        f.hole(cx - 34, rows["ammo"], D_BUTTON)
        f.hole(cx + 34, rows["ammo"], D_BUTTON)
        f.text_above(cx, rows["ammo"], D_BUTTON / 2.0, L["missiles_ammo"])
        f.text_above(cx - 34, rows["ammo"], D_BUTTON / 2.0,
                     L["missiles_ammo_prev"], TEXT_H_TINY)
        f.text_above(cx + 34, rows["ammo"], D_BUTTON / 2.0,
                     L["missiles_ammo_next"], TEXT_H_TINY)
        # 4-position type indicator: dot per type, numeral under each dot.
        for dx, name in zip((-12, -4, 4, 12), L["missiles_types"]):
            f.hole(cx + dx, rows["ammo"], D_LED_SM)
            f.text_below(cx + dx, rows["ammo"], D_LED_SM / 2.0, name,
                         TEXT_H_TINY)

        f.hole(cx, rows["load"], D_BUTTON)
        f.text_above(cx, rows["load"], D_BUTTON / 2.0, L["missiles_load"])

        f.hole(cx - 22, rows["target"], D_BUTTON)
        f.hole(cx + 22, rows["target"], D_BUTTON)
        f.text_above(cx, rows["target"], D_BUTTON / 2.0, L["missiles_target"])
        f.text_above(cx - 22, rows["target"], D_BUTTON / 2.0,
                     L["missiles_target_prev"], TEXT_H_TINY)
        f.text_above(cx + 22, rows["target"], D_BUTTON / 2.0,
                     L["missiles_target_next"], TEXT_H_TINY)

        f.hole(cx, rows["lock"], D_LED)
        f.text_below(cx, rows["lock"], D_LED / 2.0, L["missiles_lock"])

        f.hole(cx, rows["fire"], D_BUTTON)
        f.text_above(cx, rows["fire"], D_BUTTON / 2.0, L["missiles_fire"])
    f.mounts()
    return f


def f_ts_modes():
    """7.4 - Engineering, Propulsion, FTL, Turrets, Missiles, Comms, Hardpoints, Map.
    Square backlit buttons - the backlight is the selection indicator,
    so no separate LED cutout.
    8 buttons at 44 mm pitch within the 400 mm panel (10 mm inter-button
    gap); panel width unchanged so HOTAS geometry is unaffected."""
    f = Face("ts_modes")
    L = LABELS
    xs = spread(8, 44.0)
    for x, name in zip(xs, L["ts_modes_modes"]):
        f.hole(x, 0.0, BTN_SQUARE_CUTOUT)
        f.button_square(x, 0.0)
        f.text_above(x, 0.0, BTN_SQ / 2.0, name)
    f.title(L["ts_modes_title"], TEXT_H_HDR)
    f.mounts()
    return f


def f_touchscreen():
    f = Face("touchscreen")
    f.slot(0, 0, TS_W, TS_H)
    f.title(LABELS["touchscreen_title"])
    f.mounts()
    return f


def f_hotas():
    """Mounting plate only - the HOTAS units themselves are off the shelf."""
    f = Face("hotas")
    f.title(LABELS["hotas_title"])
    f.mounts(20)
    return f


def f_hardpoint():
    """7.9 - Arm, 16x1 LCD, screen, 8 soft keys, 2 encoders."""
    f = Face("hardpoint")
    L = LABELS
    f.title(L["hardpoint_title"], TEXT_H_HDR, inset=3.0)
    f.hole(-100, 130, D_TOGGLE)         # guarded arm
    f.toggle_guarded(-100, 130)
    f.text_above(-100, 130, D_TOGGLE / 2.0, L["hardpoint_arm"])
    f.slot(35, 130, 92, 20)             # 16x1 module-ID LCD
    f.text_above(35, 130, 10.0, L["hardpoint_lcd"])
    f.slot(0, 10, HP_SCREEN, HP_SCREEN)
    # Soft keys: label text comes from the screen beside each key (7.9), so
    # LABELS["hardpoint_softkeys"] is blank by default and etches nothing.
    keys = iter(L["hardpoint_softkeys"])
    for y in (70, 25, -20, -65):
        f.square(-105, y, D_BTN_SM)
        f.text_left(-105, y, D_BTN_SM / 2.0, next(keys, ""), TEXT_H_TINY)
        f.square(105, y, D_BTN_SM)
        f.text_right(105, y, D_BTN_SM / 2.0, next(keys, ""), TEXT_H_TINY)
    # Encoders - no ENC label, just the shaft holes, set a bit higher than
    # the old position so they clear the bottom soft-key row more generously.
    f.hole(-50, -100, D_ENCODER)
    f.hole(50, -100, D_ENCODER)
    f.mounts()
    return f


def f_engineering_ext():
    """Blank side extension of the engineering panel - no controls yet."""
    f = Face("engineering_ext")
    f.mounts()
    return f


def f_engineering():
    """7.8 - reactor group left, then 7 system columns.
    Repair buttons on top row, allocation encoders below."""
    f = Face("engineering")
    L = LABELS
    # Title goes top-left; centre-top is taken by the total-power gauge.
    # x is set explicitly to clear the top-left mounting hole.
    f.title(L["eng_title"], halign="left", x=-300.0)
    # reactor group
    f.hole(-310, 90, D_BUTTON)          # reactor repair priority
    f.text_above(-310, 90, D_BUTTON / 2.0, L["eng_reactor"], TEXT_H_HDR)
    f.hole(-310, -40, D_KNOB)           # reactor output
    f.text_above(-310, -40, D_KNOB / 2.0, L["eng_output"])
    f.hole(-310, -125, D_ESTOP)         # SCRAM
    f.text_above(-310, -125, D_ESTOP / 2.0, L["eng_scram"], TEXT_H_HDR)
    # Row legends sit in the deliberate gap between reactor group and systems.
    f.text(-255, 90, L["eng_row_repair"], halign="center", valign="middle")
    f.text(-255, -40, L["eng_row_alloc"], halign="center", valign="middle")
    # 7 systems: Weapons, Engines, FTL, Utility 1-4
    for x, name in zip([-200 + i * 85.0 for i in range(7)], L["eng_systems"]):
        f.hole(x, 90, D_BUTTON)         # repair priority
        f.hole(x, -40, D_ENCODER)       # allocation encoder
        # One legend per column - it names the whole vertical stack.
        f.text_below(x, -40, D_ENCODER / 2.0, name)
    f.slot(55, 138, 200, 20)            # total power available
    f.text_below(55, 138, 10.0, L["eng_total"])
    f.mounts()
    return f


# ================================================================ LAYOUT
_sw, _sh = SZ["screen"]
Z_CAM     = Z_SCREEN + _sh / 2 + SZ["cameras"][1] / 2
Z_COMMS   = Z_SCREEN - _sh / 2 - SZ["comms"][1] / 2
Z_WEAPONS = (Z_CAM + SZ["cameras"][1] / 2 + Z_COMMS - SZ["comms"][1] / 2) / 2.0
X_SIDE    = _sw / 2 + SZ["turrets"][0] / 2

TS_TILT = -55.0
_a = math.radians(90.0 + TS_TILT)
UP_Y, UP_Z = math.cos(_a), math.sin(_a)
# Top anchor = comms' own bottom-front edge, so the tilt-screen console's top
# edge actually touches comms rather than floating near it at an arbitrary
# offset. Comms front face sits at MAIN_Y - PLY_T (see f_screen's Y-facing
# convention); comms bottom edge is the same expression used for HP_Z_BOT.
TS_TOP_Y = MAIN_Y - PLY_T
TS_TOP_Z = Z_COMMS - SZ["comms"][1] / 2.0


def down_slope(d):
    return (TS_TOP_Y - UP_Y * d, TS_TOP_Z - UP_Z * d)


_y, _z = down_slope(SZ["ts_modes"][1] / 2)
TS_MODES_POS = (0.0, _y, _z)
_y, _z = down_slope(SZ["ts_modes"][1] + SZ["touchscreen"][1] / 2)
TS_POS = (0.0, _y, _z)
TS_DEPTH = SZ["ts_modes"][1] + SZ["touchscreen"][1]   # total slope run, d=0..TS_DEPTH
TS_EDGE_X = SZ["touchscreen"][0] / 2.0                 # == ts_modes half-width too
TS_Y_BOT, TS_Z_BOT = down_slope(TS_DEPTH)              # tilt-screen's own front/bottom edge

# HOTAS deck: back edge in line with the main screen/comms row, front edge
# at the tilt-screen's own front edge - nothing needs to sit forward of that
# point. Depth is therefore derived, not a fixed constant. X is derived too:
# the deck's inner edge has to land exactly on TS_EDGE_X, or the Side
# triangle (flush against the tilt-screen there) won't be flush with the
# deck itself. Z is derived the same way: the deck's underside (local z=0,
# which is world Z=pos.z here since tilt=-90/yaw=0 leave X,Y,Z unrotated)
# sits level with the tilt-screen's own front-bottom edge - the same point
# the Side triangle's base and the Back rectangle's bottom edge both sit on.
HOTAS_X = TS_EDGE_X + SZ["hotas"][0] / 2.0
HOTAS_Z = TS_Z_BOT
HOTAS_Y = (TS_Y_BOT + TS_TOP_Y) / 2.0
SZ["hotas"] = (SZ["hotas"][0], TS_TOP_Y - TS_Y_BOT)

# Hardpoint panels stack to span top-of-cameras to bottom-of-comms (see the
# SZ["hardpoint"] height derivation above), and angle outward for viewing
# like the console's other side consoles - the pivot sits on the turret's
# outer edge, so the panel's *inner* edge stays flush with it as it yaws.
HP_W, HP_H = SZ["hardpoint"]
HP_YAW = 50.0
_r = math.radians(HP_YAW)
_pivot_x = X_SIDE + SZ["turrets"][0] / 2      # turret/missile outer edge
HP_X = _pivot_x + math.cos(_r) * HP_W / 2
HP_Y = MAIN_Y - math.sin(_r) * HP_W / 2
HP_Z_TOP = (Z_CAM + SZ["cameras"][1] / 2) - HP_H / 2
HP_Z_BOT = (Z_COMMS - SZ["comms"][1] / 2) + HP_H / 2

# Propulsion/FTL fill the gap either side of HOTAS - see the WALLS section
# below for the actual (angled, non-rectangular) shape. _hotas_outer_x is
# needed there too, so it's kept as a named constant here.
_hotas_outer_x = HOTAS_X + SZ["hotas"][0] / 2.0

# Engineering: overhead panel, rear edge (local -y, away from the player -
# see the local-Y -> world derivation in placement()) anchored to the top
# of the main panel stack, i.e. cameras' own top edge - same edge-matching
# idea as the tilt-screen console's link to comms above (down_slope()), but
# engineering carries its own tilt, so it needs its own up-vector rather
# than reusing TS_TILT's.
ENG_TILT = 65.0
_eng_a = math.radians(90.0 + ENG_TILT)
ENG_UP_Y, ENG_UP_Z = math.cos(_eng_a), math.sin(_eng_a)
ENG_TOP_Y = MAIN_Y - PLY_T                       # cameras' front face
ENG_TOP_Z = Z_CAM + SZ["cameras"][1] / 2.0       # cameras' top edge
ENG_Y = ENG_TOP_Y + ENG_UP_Y * SZ["engineering"][1] / 2.0
ENG_Z = ENG_TOP_Z + ENG_UP_Z * SZ["engineering"][1] / 2.0
# Engineering's far (free) edge - local y=+h/2 - used by the WALLS section
# below to fill the gap that opens up outboard, between this edge and the
# top hardpoint panels' own outward yaw.
ENG_FAR_Y = ENG_TOP_Y + ENG_UP_Y * SZ["engineering"][1]
ENG_FAR_Z = ENG_TOP_Z + ENG_UP_Z * SZ["engineering"][1]
ENG_HALF_W = _MAIN_GROUP_W / 2.0   # full engineering group span, for the fill triangles
_eng_ext_x = (SZ["screen"][0] + SZ["engineering_ext"][0]) / 2.0

# name, builder, (x, y, z), yaw, tilt
LAYOUT = [
    ("PanelScreen",      f_screen,      (0.0, MAIN_Y, Z_SCREEN),    0.0,   0.0),
    ("PanelCameras",     f_cameras,     (0.0, MAIN_Y, Z_CAM),       0.0,   0.0),
    ("PanelComms",       f_comms,       (0.0, MAIN_Y, Z_COMMS),     0.0,   0.0),
    ("PanelTurrets",     f_turrets,     (-X_SIDE, MAIN_Y, Z_WEAPONS), 0.0,  0.0),
    ("PanelMissiles",    f_missiles,    (X_SIDE, MAIN_Y, Z_WEAPONS),  0.0,  0.0),

    ("PanelTsModes",     f_ts_modes,    TS_MODES_POS,               0.0, TS_TILT),
    ("PanelTouchscreen", f_touchscreen, TS_POS,                     0.0, TS_TILT),

    ("MountHotasLeft",   f_hotas,       (-HOTAS_X, HOTAS_Y, HOTAS_Z), 0.0, -90.0),
    ("MountHotasRight",  f_hotas,       ( HOTAS_X, HOTAS_Y, HOTAS_Z), 0.0, -90.0),

    ("PanelHardpoint1",  f_hardpoint,   (-HP_X, HP_Y, HP_Z_TOP),    HP_YAW, 0.0),
    ("PanelHardpoint2",  f_hardpoint,   (-HP_X, HP_Y, HP_Z_BOT),    HP_YAW, 0.0),
    ("PanelHardpoint3",  f_hardpoint,   ( HP_X, HP_Y, HP_Z_TOP),   -HP_YAW, 0.0),
    ("PanelHardpoint4",  f_hardpoint,   ( HP_X, HP_Y, HP_Z_BOT),   -HP_YAW, 0.0),

    # Propulsion/FTL are no longer simple flat yaw/tilt panels - they're
    # built as shaped, angled pieces in the WALLS section below.

    ("PanelEngineering",      f_engineering,     (0.0,         ENG_Y, ENG_Z), 0.0, ENG_TILT),
    ("PanelEngineeringLeft",  f_engineering_ext, (-_eng_ext_x, ENG_Y, ENG_Z), 0.0, ENG_TILT),
    ("PanelEngineeringRight", f_engineering_ext, ( _eng_ext_x, ENG_Y, ENG_Z), 0.0, ENG_TILT),
]


def placement(pos, yaw, tilt):
    """Local +Z (face normal) ends up pointing back at the player."""
    rot = (App.Rotation(App.Vector(0, 0, 1), yaw)
           .multiply(App.Rotation(App.Vector(1, 0, 0), 90.0 + tilt)))
    return App.Placement(App.Vector(*pos), rot)


# ================================================================ WALLS
# FIRST DRAFT - connecting the floating faces above into physical units.
# HOTAS's Side/Back and Propulsion/FTL's two triangular facets are all
# built as raw Part shapes here rather than via the yaw/tilt Face system,
# since none of them are flat panels facing the player.
#
# The HOTAS deck's whole footprint now runs exactly from the tilt-screen's
# front edge back to the main-screen/comms row (see the HOTAS_Y/SZ["hotas"]
# derivation above) - nothing sits forward of the tilt-screen's front edge.
# That makes both connector panels fully pinned by real geometry, no
# placeholder drop height needed:
#   Side - a right triangle. Its hypotenuse runs exactly along the tilt-
#          screen console's side edge (same maths as down_slope() above),
#          its base sits level with the screen's own front-bottom corner,
#          and its face plane is flush at x = +-TS_EDGE_X.
#   Back - a plain rectangle, flush against comms' front face, sharing its
#          inner edge with the Side triangle's vertical edge.
HOTAS_W = SZ["hotas"][0]
COMMS_FRONT_Y = TS_TOP_Y    # comms' front face - same value the tilt-screen
COMMS_BOTTOM_Z = TS_TOP_Z   # console now touches (see the TS_TOP_* fix above)


def wall_box(x0, y0, z0, dx, dy, dz):
    return Part.makeBox(dx, dy, dz, App.Vector(x0, y0, z0))


def hotas_side(sign):
    """Right triangle flush against the tilt-screen console's side edge -
    the hypotenuse (front -> back-top) lies exactly on that edge."""
    front    = (TS_Y_BOT,      TS_Z_BOT)
    back_top = (COMMS_FRONT_Y, COMMS_BOTTOM_Z)
    back_bot = (COMMS_FRONT_Y, TS_Z_BOT)
    x = sign * TS_EDGE_X
    pts = [App.Vector(x, y, z) for (y, z) in (front, back_top, back_bot, front)]
    face = Part.Face(Part.makePolygon(pts))
    return face.extrude(App.Vector(sign * PLY_T, 0, 0))


def hotas_back(sign):
    """Rectangle flush against comms' front face, sharing its inner edge
    with the Side triangle's vertical (back_top -> back_bot) edge."""
    cx = sign * HOTAS_X
    x_lo, x_hi = sorted((cx + sign * HOTAS_W / 2.0, sign * TS_EDGE_X))
    return wall_box(x_lo, COMMS_FRONT_Y - PLY_T, TS_Z_BOT,
                    x_hi - x_lo, PLY_T, COMMS_BOTTOM_Z - TS_Z_BOT)


def hotas_walls(sign, name):
    return {name + "Side": hotas_side(sign), name + "Back": hotas_back(sign)}


# Propulsion/FTL fill the remaining gap outboard of HOTAS. Four real corners
# pin this shape - not a rectangle, and not flat against the player:
#   P1 front-inner - HOTAS's own front-outer corner (touches the deck/Side)
#   P2 front-outer - the hardpoint panel's own outside-bottom corner
#   P3 back-outer  - comms' outer edge, which is also the hardpoint pivot
#                    edge (_pivot_x) - both already coincide there
#   P4 back-inner  - HOTAS's back-outer corner (the Back rectangle's own
#                    far corner)
# P1..P4 are NOT coplanar (checked: the scalar triple product is nowhere
# near zero), so this can't be one flat panel. Plywood can't take a true
# ruled twist either, so it's built as two flat triangular facets meeting
# along the P1-P3 seam:
#   Back  triangle = P1, P4, P3 - its two outer edges are flush against
#           HOTAS (P1-P4) and against comms' bottom edge (P4-P3).
#   Front triangle = P1, P3, P2 - shares the P1-P3 seam with Back, and its
#           P3-P2 edge is flush under the hardpoint panel. P2-P1 is the new
#           "front" edge - the one boundary here that isn't flush against
#           an existing neighbour, since nothing occupies that space yet.
def _hp_outer_bottom(sign):
    """The hardpoint panel's own outside-bottom corner (world coords)."""
    yaw = -sign * HP_YAW
    r = math.radians(yaw)
    lx, ly = sign * HP_W / 2.0, -HP_H / 2.0     # local: outer edge, bottom
    wx = sign * HP_X + lx * math.cos(r) + PLY_T * math.sin(r)
    wy = HP_Y + lx * math.sin(r) - PLY_T * math.cos(r)
    wz = HP_Z_BOT + ly
    return (wx, wy, wz)


def _hp_outer_top(sign):
    """The top hardpoint panel's own outside-top corner (world coords) -
    same construction as _hp_outer_bottom, mirrored to HP_Z_TOP/+HP_H/2.
    Used by the EngLeftFill/EngRightFill triangles below."""
    yaw = -sign * HP_YAW
    r = math.radians(yaw)
    lx, ly = sign * HP_W / 2.0, HP_H / 2.0      # local: outer edge, top
    wx = sign * HP_X + lx * math.cos(r) + PLY_T * math.sin(r)
    wy = HP_Y + lx * math.sin(r) - PLY_T * math.cos(r)
    wz = HP_Z_TOP + ly
    return (wx, wy, wz)


def _tri_prism(p1, p2, p3, thickness=CUT_T):
    """Generously-thick solid through 3 real 3D points, centred on their
    plane - used to trim a TriPanel blank down to its triangle outline."""
    wire = Part.makePolygon([App.Vector(*p1), App.Vector(*p2),
                             App.Vector(*p3), App.Vector(*p1)])
    face = Part.Face(wire)
    e1 = App.Vector(p2[0] - p1[0], p2[1] - p1[1], p2[2] - p1[2])
    e2 = App.Vector(p3[0] - p1[0], p3[1] - p1[1], p3[2] - p1[2])
    n = e1.cross(e2)
    n.normalize()
    face.translate(n * (-thickness / 2.0))
    return face.extrude(n * thickness)


class TriPanel(Face):
    """A Face authored in a local (u,v) grid - same hole()/slot()/text()
    calls as every other panel in this file - then mapped onto an arbitrary
    triangle in 3D and trimmed to that outline. This is what lets a
    non-rectangular connector panel reuse the whole hole-cutting/etching
    system instead of needing a parallel one.

    v is "as close to world-up as this tilted plane allows" (world Z
    projected into the plane), so authoring reads naturally - positive v is
    roughly upward, regardless of how the panel itself is angled. u is
    fixed to always point toward the player (v cross n, n pinned that way
    below) - Propulsion's and FTL's Back/Front triangles are true mirror
    images, so their local shapes come out as mirror images too, one
    negated in u relative to the other. That's why _ftl_*_controls below
    is FTL's own function with every u coordinate negated, not the same
    function reused - confirmed against the real per-side local corners,
    not assumed from the shape's symmetry."""

    def __init__(self, p1, p2, p3):
        self.p1, self.p2, self.p3 = p1, p2, p3
        P1 = App.Vector(*p1)
        e1 = App.Vector(*p2) - P1
        e2 = App.Vector(*p3) - P1
        n = e1.cross(e2)
        n.normalize()
        v = App.Vector(0, 0, 1) - n * App.Vector(0, 0, 1).dot(n)
        v.normalize()
        # Face._etch() always cuts into local +z, so +z has to be the face
        # that actually faces the player, or labels end up on the hidden
        # back face - present in the geometry, invisible in the room.
        # cross(e1,e2)'s sign depends purely on (p1,p2,p3) point order, and
        # that order flips between the mirrored left/right triangles even
        # though the resulting local (u,v) shape doesn't (checked above) -
        # so pin the real-world direction explicitly instead of trusting it.
        if n.dot(App.Vector(0, -1, 0)) < 0:
            n = n * -1.0
        u = v.cross(n)
        u.normalize()

        def to_local(p):
            d = App.Vector(*p) - P1
            return (d.dot(u), d.dot(v))

        lp = [to_local(p) for p in (p1, p2, p3)]
        us, vs = [c[0] for c in lp], [c[1] for c in lp]
        self.w, self.h = max(us) - min(us), max(vs) - min(vs)
        cx, cy = (max(us) + min(us)) / 2.0, (max(vs) + min(vs)) / 2.0
        self._origin = P1 + u * cx + v * cy   # local (0,0) = bbox centre
        self._u, self._v, self._n = u, v, n
        self.cuts = []
        self.texts = []
        self.components = []

    def matrix(self):
        """Local (u, v, n) -> world transform - the same one solid() applies
        to the panel blank, exposed so component geometry (built in the same
        local x/y coords as holes and text) can be placed onto this
        arbitrarily-oriented triangle too."""
        return App.Matrix(self._u.x, self._v.x, self._n.x, self._origin.x,
                          self._u.y, self._v.y, self._n.y, self._origin.y,
                          self._u.z, self._v.z, self._n.z, self._origin.z,
                          0, 0, 0, 1)

    def solid(self):
        blank = super(TriPanel, self).solid().copy()
        blank.transformShape(self.matrix())
        return blank.common(_tri_prism(self.p1, self.p2, self.p3))


# Back triangle: a right triangle, apex (narrow point) at local (101.75,
# -165), right angle at (101.75, 165), third corner at (-101.75, 165) - the
# full 203.5mm width is only available near v=165, tapering to nothing at
# the apex, so all 3 controls sit close to u=101.75 and are staggered
# further from it as v drops. Front triangle: apex at (49.52,-189.83),
# flat 256.2mm-wide top edge at v=189.83. Both shapes verified (offline,
# point-in-triangle check) to actually contain every hole/label placed
# here, not just their bounding boxes - the boolean trim in TriPanel.solid()
# would otherwise clip anything that strayed outside the real triangle.
# FTL is the side whose raw cross-product normal pointed away from the
# player (see the TriPanel.__init__ fix above), so its local u axis is the
# mirror of Propulsion's - every u coordinate below is negated relative to
# the _prop_*_controls layout it's otherwise a twin of.
def _ftl_back_controls(f):
    L = LABELS
    f.hole(-30, 110, D_TOGGLE)
    f.toggle_guarded(-30, 110)
    f.text_above(-30, 110, D_TOGGLE / 2.0, L["ftl_arm"])
    f.hole(-55, 0, D_BTN_LG)
    f.text_above(-55, 0, D_BTN_LG / 2.0, L["ftl_vector"])
    f.hole(-85, -110, D_BTN_LG)
    f.text_above(-85, -110, D_BTN_LG / 2.0, L["ftl_jump"])


def _ftl_front_controls(f):
    L = LABELS
    f.text(0, 175, L["ftl_title"], TEXT_H_TITLE, valign="top")
    f.hole(25, 140, D_BUTTON)           # dest prev
    f.hole(-15, 140, D_BUTTON)          # dest next
    f.text_above(5, 140, D_BUTTON / 2.0, L["ftl_dest"])
    f.text_above(25, 140, D_BUTTON / 2.0, L["ftl_dest_prev"], TEXT_H_TINY)
    f.text_above(-15, 140, D_BUTTON / 2.0, L["ftl_dest_next"], TEXT_H_TINY)


def _prop_back_controls(f):
    L = LABELS
    f.hole(40, 110, D_ESTOP)            # emergency cutoff
    f.text_above(40, 110, D_ESTOP / 2.0, L["prop_cutoff"])
    f.hole(55, 0, D_BUTTON)             # RCS
    f.text_above(55, 0, D_BUTTON / 2.0, L["prop_rcs"])
    f.hole(70, -55, D_BUTTON)           # dampeners - between RCS and reverse
    f.text_above(70, -55, D_BUTTON / 2.0, L["prop_dampeners"])
    f.hole(85, -110, D_BUTTON)          # reverse thrust
    f.text_above(85, -110, D_BUTTON / 2.0, L["prop_reverse"])


def _prop_front_controls(f):
    L = LABELS
    f.text(0, 175, L["prop_title"], TEXT_H_TITLE, valign="top")
    f.hole(-60, 140, D_TOGGLE)          # arm
    f.toggle_guarded(-60, 140)
    f.text_above(-60, 140, D_TOGGLE / 2.0, L["prop_arm"])
    f.hole(60, 140, D_KNOB)             # ignition
    f.text_above(60, 140, D_KNOB / 2.0, L["prop_ignition"])
    f.hole(10, 40, D_KNOB)              # propellant mix
    f.text_above(10, 40, D_KNOB / 2.0, L["prop_mix"])
    f.text_left(10, 40, D_KNOB / 2.0, L["prop_mix_lean"])
    f.text_right(10, 40, D_KNOB / 2.0, L["prop_mix_rich"])
    f.slot(32, -60, 50, 14)             # engine temp bargraph
    f.text_above(32, -60, 7.0, L["prop_temp"])


# Wall-object names that aren't wood (component geometry riding on a
# TriPanel) map here to their own ShapeColor; anything absent from this dict
# defaults to COL_WOOD in the BUILD section below.
WALL_COMPONENT_COLORS = {}


def propulsion_ftl_walls(sign, name, back_controls, front_controls):
    p1 = (sign * _hotas_outer_x, TS_Y_BOT, TS_Z_BOT)
    p2 = _hp_outer_bottom(sign)
    p3 = (sign * _pivot_x, TS_TOP_Y, TS_TOP_Z)
    p4 = (sign * _hotas_outer_x, TS_TOP_Y, TS_TOP_Z)
    back, front = TriPanel(p1, p4, p3), TriPanel(p1, p3, p2)
    back_controls(back)
    front_controls(front)
    result = {name + "Back": back.solid(), name + "Front": front.solid()}
    component_keys = []
    if RENDER_COMPONENTS:
        for panel, tag in ((back, "Back"), (front, "Front")):
            M = panel.matrix()
            for ci, (kind, cx, cy, extra) in enumerate(panel.components):
                for si, (shape, colour) in enumerate(component_shapes(kind, cx, cy, extra)):
                    s = shape.copy()
                    s.transformShape(M)
                    key = "%s%sComp%d_%d" % (name, tag, ci, si)
                    result[key] = s
                    WALL_COMPONENT_COLORS[key] = colour
                    component_keys.append(key)
    return result, component_keys


WALLS = {}
WALLS.update(hotas_walls(-1, "HotasLeft"))
WALLS.update(hotas_walls(1, "HotasRight"))
_prop_walls, _PROP_COMPONENT_KEYS = propulsion_ftl_walls(
    -1, "Propulsion", _prop_back_controls, _prop_front_controls)
WALLS.update(_prop_walls)
_ftl_walls, _FTL_COMPONENT_KEYS = propulsion_ftl_walls(
    1, "Ftl", _ftl_back_controls, _ftl_front_controls)
WALLS.update(_ftl_walls)

# ================================================================ BOX ENCLOSURES

def _face_box_world(w, h, pos, yaw, tilt, box_d=BOX_D):
    """Back panel + 4 side walls in local Face coords, transformed to world."""
    inner_d = box_d - PLY_T
    inner_w = w - 2 * PLY_T
    shell = Part.makeCompound([
        Part.makeBox(w, h,    PLY_T,   App.Vector(-w/2,        -h/2,        -box_d)),
        Part.makeBox(PLY_T, h, inner_d, App.Vector(-w/2,        -h/2, -box_d + PLY_T)),
        Part.makeBox(PLY_T, h, inner_d, App.Vector(w/2-PLY_T,  -h/2, -box_d + PLY_T)),
        Part.makeBox(inner_w, PLY_T, inner_d, App.Vector(-w/2+PLY_T, -h/2,       -box_d + PLY_T)),
        Part.makeBox(inner_w, PLY_T, inner_d, App.Vector(-w/2+PLY_T, h/2-PLY_T, -box_d + PLY_T)),
    ])
    shell.transformShape(placement(pos, yaw, tilt).toMatrix())
    return shell


def _bx(key, pos, yaw=0.0, tilt=0.0, box_d=BOX_D):
    return _face_box_world(SZ[key][0], SZ[key][1], pos, yaw, tilt, box_d)


# --- Touchscreen wedge: flat bottom + vertical back at the main panel wall ---
_ts_w = 2.0 * TS_EDGE_X
WALLS["TsBottom"] = Part.makeBox(
    _ts_w, TS_TOP_Y - TS_Y_BOT, PLY_T,
    App.Vector(-TS_EDGE_X, TS_Y_BOT, TS_Z_BOT))
WALLS["TsBack"] = Part.makeBox(
    _ts_w, PLY_T, TS_TOP_Z - TS_Z_BOT,
    App.Vector(-TS_EDGE_X, TS_TOP_Y - PLY_T, TS_Z_BOT))

# HOTAS / touchscreen rear extension — bottom plate + rear wall extending to
# MAIN_Y + BOX_D so the lower console has a flat back aligned with the main boxes.
_full_ts_w = 2.0 * _hotas_outer_x
WALLS["TsBottomExt"] = Part.makeBox(
    _full_ts_w, BOX_D, PLY_T,
    App.Vector(-_hotas_outer_x, MAIN_Y, TS_Z_BOT))
WALLS["TsRearWall"] = Part.makeBox(
    _full_ts_w, PLY_T, TS_TOP_Z - TS_Z_BOT,
    App.Vector(-_hotas_outer_x, MAIN_Y + BOX_D - PLY_T, TS_Z_BOT))

# --- Standard 200 mm boxes ---
WALLS["BoxScreen"]     = _bx("screen",   (0.0,    MAIN_Y, Z_SCREEN),       0.0,    0.0)
WALLS["BoxCameras"]    = _bx("cameras",  (0.0,    MAIN_Y, Z_CAM),          0.0,    0.0)
WALLS["BoxComms"]      = _bx("comms",    (0.0,    MAIN_Y, Z_COMMS),        0.0,    0.0)
WALLS["BoxTurrets"]    = _bx("turrets",  (-X_SIDE, MAIN_Y, Z_WEAPONS),     0.0,    0.0)
WALLS["BoxMissiles"]   = _bx("missiles", ( X_SIDE, MAIN_Y, Z_WEAPONS),     0.0,    0.0)
WALLS["BoxHardpoint1"] = _bx("hardpoint", (-HP_X, HP_Y, HP_Z_TOP),  HP_YAW, 0.0)
WALLS["BoxHardpoint2"] = _bx("hardpoint", (-HP_X, HP_Y, HP_Z_BOT),  HP_YAW, 0.0)
WALLS["BoxHardpoint3"] = _bx("hardpoint", ( HP_X, HP_Y, HP_Z_TOP), -HP_YAW, 0.0)
WALLS["BoxHardpoint4"] = _bx("hardpoint", ( HP_X, HP_Y, HP_Z_BOT), -HP_YAW, 0.0)

# Turret/missile to hardpoint fill: triangular prism in XY bridging the wedge
# between the turret outer wall and the hardpoint inner face.
#   C = (±pivot_x, MAIN_Y)                          — shared front corner
#   A = (±pivot_x, MAIN_Y+BOX_D)                    — turret outer back corner
#   B = (±(pivot_x+BOX_D·sin), MAIN_Y+BOX_D·cos)   — hardpoint inner face back corner
# C→A is the turret flat outer wall; C→B follows the hardpoint inner face direction.
def _turret_hp_fill(sign, z_lo, z_hi):
    r   = math.radians(HP_YAW)
    cx  = sign * _pivot_x
    bx  = sign * (_pivot_x + BOX_D * math.sin(r))
    by_ = MAIN_Y + BOX_D * math.cos(r)
    pts = [
        App.Vector(cx, MAIN_Y,         0.0),
        App.Vector(cx, MAIN_Y + BOX_D, 0.0),
        App.Vector(bx, by_,            0.0),
        App.Vector(cx, MAIN_Y,         0.0),
    ]
    face  = Part.Face(Part.makePolygon(pts))
    solid = face.extrude(App.Vector(0.0, 0.0, z_hi - z_lo))
    solid.translate(App.Vector(0.0, 0.0, z_lo))
    return solid

# One piece per hardpoint, split where the two stacked panels meet, so each half
# explodes with its own hardpoint instead of trailing into its neighbour's.
_HP_SEAM_Z = HP_Z_BOT + HP_H / 2.0
WALLS["TurretsHpFill1"]  = _turret_hp_fill(-1, _HP_SEAM_Z, ENG_TOP_Z)
WALLS["TurretsHpFill2"]  = _turret_hp_fill(-1, TS_TOP_Z, _HP_SEAM_Z)
WALLS["MissilesHpFill3"] = _turret_hp_fill(1, _HP_SEAM_Z, ENG_TOP_Z)
WALLS["MissilesHpFill4"] = _turret_hp_fill(1, TS_TOP_Z, _HP_SEAM_Z)

# Engineering enclosure. Engineering is an overhead canopy, not a front panel:
# its rear edge is pinned to cameras' top front corner, and because ENG_UP_Y
# goes negative at this tilt its far edge lands *forward* of that and higher.
# So the space it encloses sits on top of the main stack, and in side view it's
# a wedge - deepest at the back, running out to nothing where the panel's far
# edge meets the lid:
#
#     (ENG_FAR_Y, ENG_FAR_Z) ---- lid ----> (MAIN_Y+BOX_D, ENG_FAR_Z)
#            \ the panel itself                      | rear wall
#     (ENG_TOP_Y, ENG_TOP_Z) --- floor ---> (MAIN_Y+BOX_D, ENG_TOP_Z)
#
# The floor can't sit under ENG_TOP_Z the way the lid sits over ENG_FAR_Z: that
# line is the top of cameras and of the turret and missile boxes either side (all
# three come off Z_CAM + cameras/2), whose own top walls already fill the PLY_T
# below it. So the floor sits above the line, fitted between the module's end
# walls and in front of its rear wall - the same way those boxes' tops are fitted.
_ENG_SIDE_PROFILE = [
    (ENG_FAR_Y,      ENG_FAR_Z),    # panel's far edge, where it meets the lid
    (ENG_TOP_Y,      ENG_TOP_Z),    # panel's rear edge = cameras' top front corner
    (MAIN_Y + BOX_D, ENG_TOP_Z),    # back along the main boxes' tops
    (MAIN_Y + BOX_D, ENG_FAR_Z),    # up the rear wall
]


# One enclosure per engineering module - the centre, at the main panel's width,
# and a side extension out to ENG_HALF_W each way - each with its own end walls
# and floor, so every module is a closed box on its own when exploded; assembled,
# neighbouring modules' end walls just sit back to back. The panel closes the
# sloping face. The rear sits in the plane the main boxes' own back panels
# already occupy, so the console's rear stays one flat face. The lid sits ON
# ENG_FAR_Z, not inset below it: the panel's far edge is at exactly that height,
# so a lid hung downward would break out through the panel before the wedge
# runs out.
def _eng_box(x_lo, x_hi):
    def end(x, inward):
        ring = [App.Vector(x, y, z) for y, z in _ENG_SIDE_PROFILE]
        return Part.Face(Part.makePolygon(ring + [ring[0]])).extrude(
            App.Vector(inward * PLY_T, 0.0, 0.0))
    rear  = Part.makeBox(x_hi - x_lo, PLY_T, ENG_FAR_Z - ENG_TOP_Z,
                         App.Vector(x_lo, MAIN_Y + BOX_D - PLY_T, ENG_TOP_Z))
    lid   = Part.makeBox(x_hi - x_lo, MAIN_Y + BOX_D - ENG_FAR_Y, PLY_T,
                         App.Vector(x_lo, ENG_FAR_Y, ENG_FAR_Z))
    floor = Part.makeBox(x_hi - x_lo - 2 * PLY_T, MAIN_Y + BOX_D - PLY_T - ENG_TOP_Y, PLY_T,
                         App.Vector(x_lo + PLY_T, ENG_TOP_Y, ENG_TOP_Z))
    return end(x_lo, 1), end(x_hi, -1), rear, lid, floor


_eng_centre_x = SZ["engineering"][0] / 2.0
(WALLS["EngLeftSide"],   WALLS["EngLeftInner"],  WALLS["EngLeftRear"],
 WALLS["EngLeftLid"],    WALLS["EngLeftFloor"])  = _eng_box(-ENG_HALF_W, -_eng_centre_x)
(WALLS["EngEndLeft"],    WALLS["EngEndRight"],   WALLS["EngRear"],
 WALLS["EngLid"],        WALLS["EngFloor"])      = _eng_box(-_eng_centre_x, _eng_centre_x)
(WALLS["EngRightInner"], WALLS["EngRightSide"],  WALLS["EngRightRear"],
 WALLS["EngRightLid"],   WALLS["EngRightFloor"]) = _eng_box(_eng_centre_x, ENG_HALF_W)

def _hp_corner(sign):
    """The hardpoint box's silhouette in plan: its outer-front corner, round its
    outer and rear faces, to the notch's corner on the main rear wall. Shared by
    everything that hugs the hardpoints - the engineering corner above them and
    the Prop/FTL base below - so top and bottom can't drift apart."""
    r      = math.radians(HP_YAW)
    rear   = (sign * math.sin(r), math.cos(r))    # hardpoint box, front -> back
    hx, hy = _hp_outer_bottom(sign)[:2]           # same XY as _hp_outer_top
    return [
        (hx, hy),                                               # hardpoint outer front
        (hx + BOX_D * rear[0], hy + BOX_D * rear[1]),           # hardpoint outer rear
        (sign * (_pivot_x + BOX_D * math.sin(r)),
         MAIN_Y + BOX_D * math.cos(r)),                         # hardpoint inner rear
        (sign * _pivot_x,        MAIN_Y + BOX_D),               # notch -> rear wall
    ]


def _polyhedron(verts, loops):
    """Closed solid from planar faces given as vertex-index loops. Sewn, so the
    loops' winding doesn't have to agree."""
    vs    = [App.Vector(*v) for v in verts]
    shell = Part.Shell([Part.Face(Part.makePolygon([vs[i] for i in l] + [vs[l[0]]]))
                        for l in loops])
    shell.sewShape()
    solid = Part.Solid(shell)
    if solid.Volume < 0:
        solid.reverse()
    return solid


# Outboard of the shared corner the hardpoints yaw away from engineering's far
# edge. Three real corners pin the gap: the shared corner (A), the top hardpoint
# panel's outer-top corner (B) and engineering's far-top corner (D). Triangle ABD
# is the only face of the fill seen from the seat - one flat facet folding down
# off engineering's outboard edge onto the hardpoint's top edge - and all the
# bulk sits above and behind it: up to the lid's top face, and back over the
# hardpoint box and its notch along _hp_corner, the same silhouette the Prop/FTL
# base follows below. The floor lands on ENG_TOP_Z, the top of the hardpoint
# stack and of TurretsHpFill alike.
def _eng_corner(sign):
    lo, hi = ENG_TOP_Z, ENG_FAR_Z + PLY_T              # hardpoint top .. lid top
    hp = _hp_corner(sign)
    a  = (sign * ENG_HALF_W, ENG_TOP_Y, lo)             # shared corner
    d  = (sign * ENG_HALF_W, ENG_FAR_Y, ENG_FAR_Z)      # engineering far-top corner
    verts = ([a] + [(x, y, lo) for x, y in hp] +        # 0 A, 1 B, 2-4 rest of floor
             [d, (d[0], d[1], hi)] +                    # 5 D, 6 D at lid top
             [(x, y, hi) for x, y in hp])               # 7-10 top, over 1-4
    return _polyhedron(verts, [
        (0, 1, 5),              # ABD - the flat facet facing the seat
        (0, 4, 3, 2, 1),        # floor, on the hardpoint box and notch tops
        (6, 7, 8, 9, 10),       # top, flush with the lid
        (5, 1, 7, 6),           # front, standing on ABD's free edge
        (1, 2, 8, 7),           # hardpoint box's outer face, carried up
        (2, 3, 9, 8),           # ... its rear face
        (3, 4, 10, 9),          # ... and the notch's closing face
        (4, 0, 5, 6, 10),       # inboard, flat against the engineering side wall
    ])


WALLS["EngLeftFill"]  = _eng_corner(-1)
WALLS["EngRightFill"] = _eng_corner(1)

# Propulsion/FTL base plate - the outboard continuation of TsBottom/TsBottomExt,
# so all three are one PLY_T slab at desk level. Its outline is this corner's
# real outer silhouette, not a bounding box: the wing's own low apex (P1), out
# along the wing's outer edge to the hardpoint panel's outer-bottom corner (P2,
# which _hp_outer_bottom puts exactly at TS_TOP_Z), on along the hardpoint box's
# outer face, round its rear, then the notch back to the main rear wall. Traced
# in that order it comes out convex on both sides, so it cuts as one piece.
# A PLY_T plate, not a full-height solid: the wing panels slope down to P1, so
# anything taller here would burst out through them.
def _prop_ftl_outline(sign):
    """This corner's silhouette in plan - shared by the base plate and by the
    walls that stand on it, so the two can't drift apart."""
    return ([(sign * _hotas_outer_x, TS_Y_BOT)] +       # wing apex (P1)
            _hp_corner(sign) +
            [(sign * _hotas_outer_x, MAIN_Y + BOX_D)])  # rear, against HOTAS


def _prop_ftl_lower(sign):
    out  = _prop_ftl_outline(sign)
    wire = Part.makePolygon([App.Vector(x, y, TS_Z_BOT) for x, y in out] +
                            [App.Vector(out[0][0], out[0][1], TS_Z_BOT)])
    return Part.Face(wire).extrude(App.Vector(0.0, 0.0, PLY_T))


def _upright(p, q, top, centre):
    """A PLY_T wall standing on the base-plate edge p->q. `top` is its upper
    profile as (x, y, z), running back from above q to above p - a wall whose
    profile returns to plate level at one end loses that duplicated point and
    comes out a triangle. Thickness goes inboard (toward `centre`), so every
    wall's outer face stays flush with the plate's own edge."""
    ring = [App.Vector(p[0], p[1], TS_Z_BOT), App.Vector(q[0], q[1], TS_Z_BOT)]
    for t in top:
        v = App.Vector(*t)
        if (v - ring[-1]).Length > 1e-6:
            ring.append(v)
    if (ring[0] - ring[-1]).Length < 1e-6:
        ring.pop()
    n = App.Vector(q[1] - p[1], p[0] - q[0], 0.0)
    n.normalize()
    mid = App.Vector((p[0] + q[0]) / 2.0, (p[1] + q[1]) / 2.0, 0.0)
    if (centre - mid).dot(n) < 0:
        n = n * -1.0
    return Part.Face(Part.makePolygon(ring + [ring[0]])).extrude(n * PLY_T)


def _prop_ftl_uprights(sign, name):
    """One wall per base-plate edge, closing this corner from the plate up to
    the wing's top rim at TS_TOP_Z. The four edges that run under the hardpoint
    box or the rear wall are plain rectangles; the two that sit under a sloping
    wing edge take their top profile from that slope instead, so they meet the
    panel along its whole length rather than cutting through it - Outer rises
    from the wing's low apex to its P2 corner, Inboard follows the tilt-screen's
    own slope up to P4 before running flat to the rear."""
    o  = _prop_ftl_outline(sign)
    c  = App.Vector(sum(v[0] for v in o) / len(o),
                    sum(v[1] for v in o) / len(o), 0.0)
    hi, lo = TS_TOP_Z, TS_Z_BOT
    at = lambda v, z: (v[0], v[1], z)
    p4 = (sign * _hotas_outer_x, TS_TOP_Y, hi)          # the wing's own P4
    edges = [
        ("Outer",   o[0], o[1], [at(o[1], hi), at(o[0], lo)]),
        ("HpSide",  o[1], o[2], [at(o[2], hi), at(o[1], hi)]),
        ("HpRear",  o[2], o[3], [at(o[3], hi), at(o[2], hi)]),
        ("Notch",   o[3], o[4], [at(o[4], hi), at(o[3], hi)]),
        ("Rear",    o[4], o[5], [at(o[5], hi), at(o[4], hi)]),
        ("Inboard", o[5], o[0], [at(o[0], lo), p4, at(o[5], hi)]),
    ]
    return {name + k: _upright(p, q, top, c) for k, p, q, top in edges}

WALLS["PropulsionLower"] = _prop_ftl_lower(-1)
WALLS["FtlLower"]        = _prop_ftl_lower(1)
WALLS.update(_prop_ftl_uprights(-1, "Propulsion"))
WALLS.update(_prop_ftl_uprights(1, "Ftl"))


# ================================================================ BUILD
# RENDER_COMPONENTS and EXPLODE/_EXPLODE_ORIGIN are set by the combined
# STARTUP DIALOG near the top of the file - see there.
# Manufacturing groups - each explodes as a unit.
# (group_name, layout_members, walls_members)
GROUPS = [
    ("EngLeftFill",      ["PanelEngineeringLeft"],
                         ["EngLeftFill", "EngLeftSide", "EngLeftInner",
                          "EngLeftLid", "EngLeftRear", "EngLeftFloor"]),
    ("Engineering",      ["PanelEngineering"],
                         ["EngEndLeft", "EngEndRight", "EngLid", "EngRear", "EngFloor"]),
    ("EngRightFill",     ["PanelEngineeringRight"],
                         ["EngRightFill", "EngRightInner", "EngRightSide",
                          "EngRightLid", "EngRightRear", "EngRightFloor"]),
    ("Hardpoint1",       ["PanelHardpoint1"],        ["BoxHardpoint1", "TurretsHpFill1"]),
    ("Hardpoint2",       ["PanelHardpoint2"],        ["BoxHardpoint2", "TurretsHpFill2"]),
    ("Hardpoint3",       ["PanelHardpoint3"],        ["BoxHardpoint3", "MissilesHpFill3"]),
    ("Hardpoint4",       ["PanelHardpoint4"],        ["BoxHardpoint4", "MissilesHpFill4"]),
    ("Turrets",          ["PanelTurrets"],           ["BoxTurrets"]),
    ("Missiles",         ["PanelMissiles"],          ["BoxMissiles"]),
    ("ScreenCameras",    ["PanelScreen", "PanelCameras"], ["BoxScreen", "BoxCameras"]),
    ("Comms",            ["PanelComms"],             ["BoxComms"]),
    ("TouchscreenHotas", ["PanelTsModes", "PanelTouchscreen",
                          "MountHotasLeft", "MountHotasRight"],
                         ["HotasLeftSide", "HotasLeftBack",
                          "HotasRightSide", "HotasRightBack",
                          "TsBottom", "TsBack",
                          "TsBottomExt", "TsRearWall"]),
    ("FTL",              [],  ["FtlBack", "FtlFront", "FtlLower",
                               "FtlOuter", "FtlHpSide", "FtlHpRear",
                               "FtlNotch", "FtlRear", "FtlInboard"]
                              + _FTL_COMPONENT_KEYS),
    ("Propulsion",       [],  ["PropulsionBack", "PropulsionFront", "PropulsionLower",
                               "PropulsionOuter", "PropulsionHpSide", "PropulsionHpRear",
                               "PropulsionNotch", "PropulsionRear", "PropulsionInboard"]
                              + _PROP_COMPONENT_KEYS),
]

# Pre-build all shapes so centroid computation (bounding-box) is available.
# The Face instance itself is kept too (not just its solid()) so its
# registered .components can be placed in the BUILD loop below, reusing the
# same (pos, yaw, tilt) placement as the panel they're mounted on.
_layout_built = {}
_layout_faces = {}
for name, builder, pos, yaw, tilt in LAYOUT:
    face_obj = builder()
    _layout_built[name] = (face_obj.solid(), pos, yaw, tilt)
    _layout_faces[name] = face_obj

_layout_pos = {name: App.Vector(*pos) for name, _, pos, __, ___ in LAYOUT}

_wall_centre = {}
for name, shape in WALLS.items():
    bb = shape.BoundBox
    _wall_centre[name] = App.Vector(
        (bb.XMin + bb.XMax) / 2,
        (bb.YMin + bb.YMax) / 2,
        (bb.ZMin + bb.ZMax) / 2)

_objs = {}
for gname, layout_members, walls_members in GROUPS:
    pts = ([_layout_pos[n] for n in layout_members] +
           [_wall_centre[n] for n in walls_members])
    cx = sum(p.x for p in pts) / len(pts)
    cy = sum(p.y for p in pts) / len(pts)
    cz = sum(p.z for p in pts) / len(pts)
    centroid = App.Vector(cx, cy, cz)

    offset = App.Vector(0, 0, 0)
    if EXPLODE > 0.0:
        _d = centroid - _EXPLODE_ORIGIN
        if _d.Length > 1e-6:
            _d.normalize()
            offset = _d * EXPLODE

    for name in layout_members:
        shape, pos, yaw, tilt = _layout_built[name]
        epos = App.Vector(*pos) + offset
        panel_placement = placement((epos.x, epos.y, epos.z), yaw, tilt)
        obj = doc.addObject("Part::Feature", name)
        obj.Shape = shape
        obj.Placement = panel_placement
        if obj.ViewObject:
            obj.ViewObject.ShapeColor = COL_WOOD
        _objs[name] = obj

        if RENDER_COMPONENTS:
            for ci, (kind, cx, cy, extra) in enumerate(_layout_faces[name].components):
                for si, (cshape, colour) in enumerate(component_shapes(kind, cx, cy, extra)):
                    cobj = doc.addObject("Part::Feature", "%s_Comp%d_%d" % (name, ci, si))
                    cobj.Shape = cshape
                    cobj.Placement = panel_placement
                    if cobj.ViewObject:
                        cobj.ViewObject.ShapeColor = colour
                    _objs[cobj.Name] = cobj

    for name in walls_members:
        moved = WALLS[name].copy()
        moved.translate(offset)
        obj = doc.addObject("Part::Feature", name)
        obj.Shape = moved
        if obj.ViewObject:
            obj.ViewObject.ShapeColor = WALL_COMPONENT_COLORS.get(name, COL_WOOD)
        _objs[name] = obj

doc.recompute()

# Real (FreeCAD-measured, not eyeballed) clearances between the HOTAS boxes
# and their neighbours - this is what should drive the next connector pass.
def _gap(a, b):
    return _objs[a].Shape.distToShape(_objs[b].Shape)[0]


App.Console.PrintMessage("\nHOTAS connector contact check (mm, want ~0):\n")
for a, b in [("HotasLeftSide",  "PanelTouchscreen"),
             ("HotasLeftBack",  "PanelComms"),
             ("HotasRightSide", "PanelTouchscreen"),
             ("HotasRightBack", "PanelComms")]:
    App.Console.PrintMessage("  %-16s -> %-16s  %6.1f\n" % (a, b, _gap(a, b)))

App.Console.PrintMessage("\nPropulsion/FTL connector contact check (mm, want ~0):\n")
for a, b in [("PropulsionBack",  "MountHotasLeft"),
             ("PropulsionBack",  "PanelComms"),
             ("PropulsionFront", "PanelHardpoint2"),
             ("FtlBack",         "MountHotasRight"),
             ("FtlBack",         "PanelComms"),
             ("FtlFront",        "PanelHardpoint4")]:
    App.Console.PrintMessage("  %-16s -> %-16s  %6.1f\n" % (a, b, _gap(a, b)))

App.Console.PrintMessage("\nEngineering connector contact check (mm, want ~0):\n")
for a, b in [("PanelEngineering", "PanelCameras"),
             ("EngLeftFill",      "PanelEngineering"),
             ("EngLeftFill",      "PanelCameras"),
             ("EngLeftFill",      "PanelHardpoint1"),
             ("EngRightFill",     "PanelEngineering"),
             ("EngRightFill",     "PanelCameras"),
             ("EngRightFill",     "PanelHardpoint3")]:
    App.Console.PrintMessage("  %-16s -> %-16s  %6.1f\n" % (a, b, _gap(a, b)))

try:
    import FreeCADGui
    FreeCADGui.SendMsgToActiveView("ViewFit")
    FreeCADGui.activeDocument().activeView().viewAxonometric()
except Exception:
    pass

App.Console.PrintMessage(
    "Cold Orbit console: %d panels, %.1f mm ply\n" % (len(LAYOUT), PLY_T))
App.Console.PrintMessage(
    "Player eye reference: (0, 0, %.0f)\n" % EYE_Z)
if SHOW_LABELS and not _FONT:
    App.Console.PrintWarning(
        "No font found - panels built without etched labels, set FONT_FILE\n")
elif SHOW_LABELS:
    App.Console.PrintMessage(
        "Labels etched %.1f mm deep using %s\n" % (ETCH_D, _FONT))
